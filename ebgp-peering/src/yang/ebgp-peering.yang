module ebgp-peering {
  namespace "http://com/example/ebgppeering";
  prefix ebgp-peering;

  import ietf-inet-types {
    prefix inet;
  }
  import tailf-ncs {
    prefix ncs;
  }

  augment /ncs:services {
    list ebgp-peering {
      key name;

      uses ncs:service-data;
      ncs:servicepoint "ebgp-peering";

      leaf name {
        type string;
      }

      // may replace this with other ways of refering to the devices.
      leaf-list device {
        type leafref {
          path "/ncs:devices/ncs:device/ncs:name";
        }
      }

      // replace with your own stuff here
      leaf dummy {
        type inet:ipv4-address;
      }
    }
  }
}
