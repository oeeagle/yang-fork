module chtr-snmp {
    namespace "http://com/example/chtr-snmp";
    prefix chtr-snmp;

    import ietf-inet-types { prefix inet; }
    import tailf-ncs { prefix ncs; }
    import tailf-common { prefix tailf; }

    description
        "";

    revision 2015-11-02 {
        description
                "initial model: The goal of this service is to support the user
                input of 'set service chtr-snmp <name> [device] <SNMP-host-1>
                <SNMP-host-2> <SNMP-host-3>' where name describes the NTP service,
                device is a list <SNMP-host-1> is madatory and <SNMP-host-2> and
                <SNMP-host-3> are optional Each service instance is made unique
                by the declaraion of <name> and the ordered combination of SNMP-hosts.
                The devices added to this service act as subscribers to the service
                RATHER than the service being dependent upon the devices";
    }

    augment "/ncs:services" {
        list chtr-snmp {
            description "";
            key "name";
            uses ncs:service-data;
            ncs:servicepoint "chtr-snmp";
            leaf name {
                description
                                "SNMP group name";
                tailf:info "SNMP group name";
                type string;
            }

            container node-list {
                list device {
                    description "";
                    key "name city state realestate-id";
                    leaf name {
                        description
                                                "";
                        type leafref {
                            path "/ncs:devices/ncs:device/ncs:name";
                        }
                    }
                    leaf city {
                        type string {
                            length "4";
                        }
                    }
                    leaf state {
                        type string {
                            length "2";
                        }
                    }
                    leaf realestate-id {
                        type string {
                            length "6";
                        }
                    }
                }
            }
            container community-list {
                list community {
                    key "type id";
                    description
                                        "";
                    leaf type {
                        description "";
                        type enumeration {
                            enum read-only;
                            enum read-write;
                        }
                        default "read-only";
                    }
                    leaf id {
                        type string {
                        }
                    }
                    leaf address-family {
                        description "";
                        mandatory "true";
                        type enumeration {
                            enum inet4;
                            enum inet6;
                        }
                    }
                    choice acl {
                        description "";
                        case ipv4 {
                            when "address-family='inet4'";
                            leaf inet4-acl {
                                description "";
                                type leafref {
                                    path "/ncs:services/chtr-snmp:chtr-snmp[chtr-snmp:name=current()/../../../name]/chtr-snmp:access-list/chtr-snmp:inet4/chtr-snmp:named-acl/chtr-snmp:name";
                                }
                            }
                        }
                        case ipv6 {
                            when "address-family='inet6'";
                            leaf inet6-acl {
                                description "";
                                type leafref {
                                    path "/ncs:services/chtr-snmp:chtr-snmp[chtr-snmp:name=current()/../../../name]/chtr-snmp:access-list/chtr-snmp:inet6/chtr-snmp:named-acl/chtr-snmp:name";
                                }
                            }
                        }
                    }
                }
            }

            container access-list {
                description "";

                container inet4 {
                    list named-acl {

                        key name;
                        leaf name {
                            type string {
                                tailf:info "WORD;;User selected string identifying this "                                +
                                                                "access list";
                            }
                        }
                        list rule {
                            key "id";
                            leaf id {
                                type uint32 {
                                    tailf:info "<1-2147483644>;;Sequence number for this entry";
                                }
                            }

                            // FIXME: create better data model for this, probably a choice along
                            // the lines of
                            // choice rule-choice {
                            //   container permit {
                            //   }
                            //   container deny {
                            //   }
                            //   container remark {
                            //   }
                            // }

                            leaf line {

                                type string {
                                    tailf:info "deny - Specify packets to reject\n"                                    + "permit;;Specify packets to forward\n"                                    +
                                                                        "remark;;Comment for access list";
                                    pattern "(deny.*)|(permit.*)|(remark.*)|(no.*)";
                                }
                            }
                        }
                    }
                }
                    container inet6 {
                        list named-acl {

                            key name;
                            leaf name {
                                type string {
                                    tailf:info "WORD;;User selected string identifying this "                                    +
                                                                        "access list";
                                }
                            }
                            list rule {
                                key "id";
                                leaf id {
                                    type uint32 {
                                        tailf:info "<1-2147483644>;;Sequence number for this entry";
                                    }
                                }

                                // FIXME: create better data model for this, probably a choice along
                                // the lines of
                                // choice rule-choice {
                                //   container permit {
                                //   }
                                //   container deny {
                                //   }
                                //   container remark {
                                //   }
                                // }

                                leaf line {

                                    type string {
                                        tailf:info "deny - Specify packets to reject\n"                                        + "permit;;Specify packets to forward\n"                                        +
                                                                                "remark;;Comment for access list";
                                        pattern "(deny.*)|(permit.*)|(remark.*)|(no.*)";
                                    }
                                }
                            }
                        }
                    }
                }
            }
        }
}
