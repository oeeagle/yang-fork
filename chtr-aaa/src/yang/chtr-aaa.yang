module chtr-aaa {
  namespace "http://com/example/chtr-aaa";
  prefix chtr-aaa; 
  
  import ietf-inet-types {
    prefix inet;
  }
  import tailf-ncs {
    prefix ncs;
  }
  import tailf-common {
    prefix tailf;
  }
  import entity {
    prefix entity;
  }

  description
    "";

  revision 2015-11-02 {
    description
      "initial model:
       The goal of this service is to support the user input of 'set service chtr-aaa <name> [device] <aaa-host-1> <aaa-host-2> <aaa-host-3>'
       where name describes the NTP service, device is a list <aaa-host-1> is madatory and <aaa-host-2> and <aaa-host-3> are optional
       Each service instance is made unique by the declaraion of <name> and the ordered combination of aaa-hosts. The devices added to
       this service act as subscribers to the service RATHER than the service being dependent upon the devices";
  }

  augment "/ncs:services" {
    list chtr-aaa {
      key "name";
      uses ncs:service-data;
      ncs:servicepoint "chtr-aaa";
      leaf name {
        description
          "AAA authentication group name";
        tailf:info  "AAA authentication device group name";
        type string;
      }
      leaf device {
          description
                  "";
          type leafref {
              path "/ncs:devices/ncs:device/ncs:name";
          }
        must "count(../../chtr-aaa[name != current()/../name][device = current()/../device]) = 0";
      }
      container local-auth {
        leaf local-username {
          tailf:info "shared secret";
          type string;
        }
        leaf vtypass {
          tailf:info "shared secret";
          type string;
        }
        leaf enablepass {
          tailf:info "shared secret";
          type string;
        }
      }
      container remote-auth {
        leaf aaa-shared-secret {
        	mandatory true;
          tailf:info "shared secret";
          type string;
        }
        leaf aaa-host-1 {
          mandatory true;
          tailf:info "Primary AAA Server, this entry is required";
          type union {
            type inet:ipv4-address;
            type inet:ipv6-address;
          }
        }
        leaf aaa-host-2 {
          tailf:info "Secondary AAA Server, this entry is optional";
          type union {
            type inet:ipv4-address;
            type inet:ipv6-address;
          }
        }
        leaf aaa-host-3 {
          tailf:info "Tertiary AAA Server, this entry is optional";
          type union {
            type inet:ipv4-address;
            type inet:ipv6-address;
          }
        }
      }
    }
  }
}
