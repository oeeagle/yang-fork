module engdb {
  namespace "http://charterlab.com/example/engdb";
  prefix engdb;

  include engdb-types;
  include engdb-role;
  


  organization "Charter Engineering";
  contact
    "bill.armstrong@charter.com";
  description
    "This is the Charter Engineering Datastore YANG module. The Goal of this module is the provide a facility that exposes Engineering certified attributes to aid in the creation of services";

  revision 2015-08-03 {
	    description
	      "Created region and added more types";
	  }

}
