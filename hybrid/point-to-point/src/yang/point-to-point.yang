module point-to-point {
  namespace "http://com/example/pointtopoint";
  prefix point-to-point;

  import ietf-inet-types {
    prefix inet;
  }
  import tailf-common {
    prefix tailf;
  }
  import tailf-ncs {
    prefix ncs;
  }

  augment /ncs:services {

    list point-to-point {
      description "This is an RFS skeleton service";

      key name;
      leaf name {
        tailf:info "Unique service id";
        tailf:cli-allow-range;
        type string;
      }

      // may replace this with other ways of refering to the devices.
      leaf-list device {
        type leafref {
          path "/ncs:devices/ncs:device/ncs:name";
        }
      }

      uses ncs:service-data;
      ncs:servicepoint point-to-point-servicepoint;

      tailf:action self-test {
        tailf:info "Perform self-test of the service";
        tailf:actionpoint point-to-point-self-test;
        output {
          leaf success {
            type boolean;
          }
          leaf message {
            type string;
            description
              "Free format message.";
          }
        }
      }
      // replace with your own stuff here
      leaf dummy {
        type inet:ipv4-address;
      }
    }
  }
}
